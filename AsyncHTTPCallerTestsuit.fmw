FME workspace AsyncHTTPCallerTestsuit.fmw
Title: Test suit for AsyncHTTPCaller
Description: Testsuit AsyncHTTPCaller
This is the Testsuit for AsyncHTTPCaller. It will collect som files online and the async httpcaller will try to asyncronously download each file either as an attribute or as a file.
PIP Requirements for the AsyncHTTPCaller is aiofiles and aiohttp. The transformer will do an attempt to install these, but its not guaranteed to work. Im unable to pass the test on hub.safe.com.
send a message to paalped(at)gmail.com if you have any questions.
Paal

PythonCreator_2
    NEW_ATTRIBUTES = link
    PYTHONSOURCE_NEW:
      import fmeobjects

      # Template Class
      class FeatureCreator(object):
          def __init__(self):
              pass
          def input(self,feature):
              samples = ['https://images.examples.com/wp-content/uploads/2017/05/Reflective-Essay.zip',
              'https://images.examples.com/wp-content/uploads/2017/05/Autobiography-Example.zip',
              'https://images.examples.com/wp-content/uploads/2017/06/Sample-Descriptive.zip']
              for link in samples:
                  # input method must be defined
                  #
                  # output features here to create the features
                  # before reader features have been processed
                  newFeature = fmeobjects.FMEFeature()
                  newFeature.setAttribute('link', link)

                  self.pyoutput(newFeature)
          def close(self):
              # close method must be defined
              #
              # output features here to create the features
              # after reader features have been processed
              pass
    PYTHONSYMBOL = FeatureCreator
    -> AsyncHTTPCaller
AsyncHTTPCaller
    attribute_name = _response_body
    bool_file_or_attribute = Attribute
    group_num = 100
    http_method = GET
    url = link
    -> AsyncHTTPCaller_Output
    <Rejected> -> AsyncHTTPCaller__Rejected_
AsyncHTTPCaller_Output: Inspector
AsyncHTTPCaller__Rejected_: Inspector
